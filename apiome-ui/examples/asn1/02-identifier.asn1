-- ASN.1 example — identifier CHOICE and item record.
--
-- Demonstrates CHOICE unions and DEFAULT values alongside ENUMERATED types.
IdentifierModule DEFINITIONS AUTOMATIC TAGS ::= BEGIN

  Color ::= ENUMERATED { red(0), green(1), blue(2) }

  Identifier ::= CHOICE {
    id    INTEGER,
    code  UTF8String
  }

  Item ::= SEQUENCE {
    name  UTF8String,
    color Color DEFAULT red
  }

END
