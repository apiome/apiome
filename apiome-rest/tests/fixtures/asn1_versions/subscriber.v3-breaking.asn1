-- ASN.1 version fixture (MFI-21.5, #3995): a subscriber-provisioning module, v3 — breaking against
-- v1: a mandatory component added to the root, a DEFAULT changed, a range narrowed, a tag
-- renumbered, components swapped, an alternative removed and the extension marker dropped.
--
-- Exercises what the ASN.1 diff grades: explicit tags, an extension marker with an extension
-- addition, OPTIONAL and DEFAULT components, a value range and a SIZE constraint, an extensible
-- ENUMERATED, a CHOICE, and a SET.
Subscriber-Provisioning DEFINITIONS IMPLICIT TAGS ::= BEGIN

  ServiceClass ::= ENUMERATED { basic(0), premium(1) }

  Identity ::= CHOICE {
    imsi    [0] OCTET STRING (SIZE (3..8))
  }

  Location ::= SET {
    cellId  [0] INTEGER (0..65535),
    lac     [1] INTEGER (0..65535)
  }

  Subscriber ::= SEQUENCE {
    identity      [0] Identity,
    maxSessions   [2] INTEGER (1..8) DEFAULT 2,
    serviceClass  [1] ServiceClass DEFAULT basic,
    displayName   [7] UTF8String (SIZE (1..64)) OPTIONAL,
    tenant        [8] UTF8String,
    location      [4] Location OPTIONAL,
    ...,
    roaming       [5] BOOLEAN OPTIONAL
  }

END
